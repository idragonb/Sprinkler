(defun c:css (/ poly offset objpoly)
   (setq poly (car (entsel "\nPick polyline representing boundary...")))
   (setq objpoly (vlax-ename->vla-object poly))
   (connectsprinkler objpoly offset)
)

(defun connectsprinkler (objpoly offset / sprinkler objsprinkler objarms)
  (while   (setq sprinkler (car (entsel "\nPick on sprinkler...")))
      (setq objsprinkler (vlax-ename->vla-object sprinkler))
	  (setq offset (getoffset "Offset" objsprinkler))
	  (if (setq objarms (getsprinklerarms objsprinkler))
         (move-to-edge objarms objpoly offset)
	  )
   )
 )
 
 (defun getoffset (chktag objsprinkler)
   (setq atts (vlax-variant-value (vlax-invoke-method obj 'GetAttributes)))
   (setq nn 0)
   (setq lower (vlax-safearray-get-l-bound atts 1))
   (setq upper (vlax-safearray-get-u-bound atts 1))
   (while (<= nn upper)
      (setq att (vlax-safearray-get-element atts nn))
	  (setq tag (vlax-get-property att 'TagString))
	  (setq val (vlax-get-property att 'TextString))
	  (if (= tag chktag)
		(setq retval (atof val))
	  )
	  (setq nn (1+ nn))
	)
	retval
)
 
(defun move-to-edge (objsprinkler objpoly offset / pt-sprinkler ptnear ptnew)
(princ "\n000")
    (setq pt-sprinkler (get-sprinkler-origin objsprinkler))
	(princ "\n011")
    (setq ptnear (get-closest-point pt-sprinkler objpoly))
	(princ "\n022")
	(setq ptnew (polar ptnear (angle ptnear  (vlax-safearray->list (vlax-variant-value pt-sprinkler))) offset))
	(princ "\n033")
	(add-vertices-to-poly objpoly ptnew ptnear offset)
	(princ "\n044")
	(move-sprinkler objsprinkler ptnew)
	(princ "\n055")
)

(defun add-vertices-to-poly (objpoly ptnew ptnear offset / coords first final nn ptfirst x y addit pt1 pt2)
   (setq coords (vlax-variant-value (vlax-get-property objpoly 'Coordinates)))
   (setq first (vlax-safearray-get-l-bound coords 1))
   (setq final (vlax-safearray-get-u-bound coords 1))
   (setq nn first)
   (setq ptfirst nil)
   (princ "\n034")
   (while (< nn final)
      (setq x (vlax-safearray-get-element coords nn))
	  (setq nn (1+ nn))
	  (setq y (vlax-safearray-get-element coords nn))
      (setq nn (1+ nn))
	  (setq pt2 (list x y))
	  (princ "\n035")
	  (if (not ptfirst)
	     (setq ptfirst pt2)
		 (progn
			(if (inters pt1 pt2 ptnew (list 0 0.1) T)
               (progn
			       ; (vlax-invoke-method mspace 'AddLine (vlax-3D-point pt1) (vlax-3D-point pt2 ))
					;(princ nn)
					;(getstring "\n")
					(if flag
					    (setq addit -1)
						(setq addit 0)
					)
					(vlax-invoke-method objpoly 'AddVertex (+ addit (/ mincount 2)) (vlax-2D-point ptnear))
					(vlax-invoke-method objpoly 'AddVertex (+ addit (/ mincount 2)) (vlax-2D-point ptnew )) ; if offset > 0
					(if flag
						(vlax-invoke-method objpoly 'AddVertex (+ addit (/ mincount 2)) (vlax-2D-point ptnear))
					)
					;(vlax-invoke-method mspace 'AddLine (vlax-3D-point ptnear) (vlax-3D-point ptnew ))
					;(vlax-invoke-method objpoly 'AddVertex 0 (vlax-2D-point (getpoint)))
				)
            )
         )	
		 
	  )
	  (setq pt1 pt2)
   )
 )

(defun vlax-2D-point (pt)
	(vlax-make-variant
		(vlax-safearray-fill
			(vlax-make-safearray vlax-vbdouble (cons 0 1))
				(list
					(nth 0 pt)
					(nth 1 pt)
				)
		)
	)
)

(defun move-sprinkler (objsprinkler ptnew)
   (vlax-put-property objsprinkler 'InsertionPoint (vlax-3D-point ptnew))
)

(defun get-closest-point (pt-sprinkler objpoly / coords pt3 x y nn first final ptfirst mindist pt2 pt4 pt6 pt5 minpoint mindist)
   (setq pt3 (vlax-safearray->list (vlax-variant-value pt-sprinkler)))			; get sprinkler origin
   (setq coords (vlax-variant-value (vlax-get-property objpoly 'Coordinates)))	; polyline coordinates
 
   (setq first (vlax-safearray-get-l-bound coords 1))
   (setq final (vlax-safearray-get-u-bound coords 1))
   (setq nn first)
   (setq ptfirst nil)
   (setq mindist nil)
   (setq flag nil)
   (while (< nn final)
      (setq x (vlax-safearray-get-element coords nn))
	  (setq nn (1+ nn))
	  (setq y (vlax-safearray-get-element coords nn))
      (setq nn (1+ nn))
	  (setq pt2 (list x y))
	  (if (not ptfirst)
	     (setq ptfirst pt2)
		 (progn
		    (setq ang (angle pt1 pt2))
			;(setq pt3 pt-sprinkler)
			(setq pt4 (polar pt3 (+ ang (/ pi 2)) 10000))
			(setq pt6 (polar pt3 (- ang (/ pi 2)) 10000))
			(if (setq pt5 (inters pt1 pt2 pt6 pt4 T))
			   (if (or (< (setq curmindist (distance pt3 pt5)) mindist)(= mindist nil))
			      (progn
			         (setq mindist curmindist)
					 (setq minpoint pt5)
					 (setq mincount nn)
					 (setq flag T)
				  )
			   )
			   (if (> (distance pt1 pt3) (distance pt2 pt3))
			      (if (or (< (setq curmindist (distance pt2 pt3)) mindist)(= mindist nil))
			         (progn
			            (setq mindist curmindist)
		    		    (setq minpoint pt2)
					    (setq mincount nn)
				      )
                  )	 	    
	              (if (or (< (setq curmindist (distance pt1 pt3)) mindist)(= mindist nil))
			         (progn
			            (setq mindist curmindist)
		    		    (setq minpoint pt1)
					    (setq mincount nn)
				     )
                  )
                )
              )
              
            )
         )	
		 (setq pt1 pt2)
	  )
	  minpoint
)


(defun get-sprinkler-origin (objsprinkler)
   (vlax-get-property objsprinkler 'InsertionPoint)
)

(defun getsprinklerarms (objsprinkler / handle arms obj-arms)
   (if (/= (vlax-get-property objsprinkler 'EffectiveName) "sprinkler")
      (progn
	     (setq handle (vlax-get-property objsprinkler 'Name))
		 (if (setq arms (handent handle))
		    (setq obj-arms (vlax-ename->vla-object arms))
			(setq obj-arms nil)
		 )
	  )
	  (setq obj-arms objsprinkler)
	)
	obj-arms
)
