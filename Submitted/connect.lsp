(defun c:css ()
   (setq poly (car (entsel "\nPick polyline representing boundary...")))
   (setq offset (getreal "\nEnter desired offset"))
   (setq objpoly (vlax-ename->vla-object poly))
   (connectsprinkler objpoly offset)
)

(defun connectsprinkler (objpoly offset)
   (while (setq sprinkler (car (entsel "\nPick on sprinkler...")))
      (setq objsprinkler (vlax-ename->vla-object sprinkler))
	  (if (setq objarms (getsprinklerarms objsprinkler))
         (move-to-edge objarms objpoly offset)
	  )
   )
 )
 
(defun move-to-edge (objsprinkler objpoly offset)
(princ "\n000")
    (setq pt-sprinkler (get-sprinkler-origin objsprinkler))
	(princ "\n011")
    (setq ptnear (get-closest-point pt-sprinkler objpoly))
	(princ "\n022")
	(setq ptnew (polar ptnear (angle ptnear  (vlax-safearray->list (vlax-variant-value pt-sprinkler))) offset))
	(princ "\n033")
	(add-vertices-to-poly objpoly ptnew ptnear offset)
	(princ "\n044")
	(move-sprinkler objsprinkler ptnew)
	(princ "\n055")
)

(defun add-vertices-to-poly (objpoly ptnew ptnear offset)
   (setq coords (vlax-variant-value (vlax-get-property objpoly 'Coordinates)))
   (setq first (vlax-safearray-get-l-bound coords 1))
   (setq last (vlax-safearray-get-u-bound coords 1))
   (setq nn first)
   (setq ptfirst nil)
   (princ "\n034")
   (while (< nn last)
      (setq x (vlax-safearray-get-element coords nn))
	  (setq nn (1+ nn))
	  (setq y (vlax-safearray-get-element coords nn))
      (setq nn (1+ nn))
	  (setq pt2 (list x y))
	  (princ "\n035")
	  (if (not ptfirst)
	     (setq ptfirst pt2)
		 (progn
			(if (inters pt1 pt2 ptnew (list 0 0.1) T)
               (progn
			   (princ "\n036")

					(princ "\n037")
					(vlax-invoke-method objpoly 'AddVertex (- nn 3) (vlax-2D-point ptnear))
					(vlax-invoke-method objpoly 'AddVertex (- nn 3) (vlax-2D-point ptnew )) ; if offset > 0
					(vlax-invoke-method objpoly 'AddVertex (- nn 3) (vlax-2D-point ptnear))
				;	(vlax-invoke-method mspace 'AddLine (vlax-3D-point ptnear) (vlax-3D-point ptnew ))
				)
            )
         )	
		 
	  )
	  (setq pt1 pt2)
   )
 )

(defun vlax-2D-point (pt)
	(vlax-make-variant
		(vlax-safearray-fill
			(vlax-make-safearray vlax-vbdouble (cons 0 1))
				(list
					(nth 0 pt)
					(nth 1 pt)
				)
		)
	)
)

(defun move-sprinkler (objsprinkler ptnew)
   (vlax-put-property objsprinkler 'InsertionPoint (vlax-3D-point ptnew))
)

(defun get-closest-point (pt-sprinkler objpoly / x y nn first last)
   (setq pt3 (vlax-safearray->list (vlax-variant-value pt-sprinkler)))
   (setq coords (vlax-variant-value (vlax-get-property objpoly 'Coordinates)))
 
   (setq first (vlax-safearray-get-l-bound coords 1))
   (setq last (vlax-safearray-get-u-bound coords 1))
   (setq nn first)
   (setq ptfirst nil)
   (setq mindist nil)
   (while (< nn last)
      (setq x (vlax-safearray-get-element coords nn))
	  (setq nn (1+ nn))
	  (setq y (vlax-safearray-get-element coords nn))
      (setq nn (1+ nn))
	  (setq pt2 (list x y))
	  (if (not ptfirst)
	     (setq ptfirst pt2)
		 (progn
		    (setq ang (angle pt1 pt2))
			;(setq pt3 pt-sprinkler)
			(setq pt4 (polar pt3 (+ ang (/ pi 2)) 10000))
			(setq pt6 (polar pt3 (- ang (/ pi 2)) 10000))
			(if (setq pt5 (inters pt1 pt2 pt6 pt4 T))
			   (if (or (< (setq curmindist (distance pt3 pt5)) mindist)(= mindist nil))
			      (progn
			         (setq mindist curmindist)
					 (setq minpoint pt5)
					 (setq mincount nn)
				  )
			   )
			   (if (> (distance pt1 pt3) (distance pt2 pt3))
			      (if (or (< (setq curmindist (distance pt2 pt3)) mindist)(= mindist nil))
			         (progn
			            (setq mindist curmindist)
		    		    (setq minpoint pt2)
					    (setq mincount nn)
				      )
                  )	 	    
	              (if (or (< (setq curmindist (distance pt1 pt3)) mindist)(= mindist nil))
			         (progn
			            (setq mindist curmindist)
		    		    (setq minpoint pt1)
					    (setq mincount nn)
				     )
                  )
                )
              )
              
            )
         )	
		 (setq pt1 pt2)
	  )
	  minpoint
)


(defun get-sprinkler-origin (objsprinkler)
   (vlax-get-property objsprinkler 'InsertionPoint)
)

(defun getsprinklerarms (objsprinkler)
   (if (/= (vlax-get-property objsprinkler 'EffectiveName) "sprinkler")
      (progn
	     (setq handle (vlax-get-property objsprinkler 'Name))
		 (if (setq arms (handent handle))
		    (setq obj-arms (vlax-ename->vla-object arms))
			(setq obj-arms nil)
		 )
	  )
	  (setq obj-arms objsprinkler)
	)
	obj-arms
)
